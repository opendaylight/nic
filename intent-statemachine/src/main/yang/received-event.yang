module received-event {
    namespace "urn:opendaylight:nic:received:event";
    prefix "received-event";

    description
        "This module represents a wrapper for Intent and Network events.";

    revision 2015-12-02 {
        description "Initial revision.";
    }

    typedef received-event {
        type enumeration {
            enum NODEUP;
            enum NODEUPDATED;
            enum NODEDOWN;
            enum SWITCHUP;
            enum SWITCHDOWN;
            enum INTENTCREATED;
            enum INTENTUPDATED;
            enum INTENTREMOVED;
        }
        description "Wrapper for Intent and Network events.";
    }
}
