//-------------------------------------------------------------------------------------
// Copyright (c) 2017 Serro LLC.  All rights reserved.
//
// This program and the accompanying materials are made available under the
// terms of the Eclipse Public License v1.0 which accompanies this distribution,
// and is available at http://www.eclipse.org/legal/epl-v10.html
//-------------------------------------------------------------------------------------
module intent-state-transaction {
    namespace "urn:opendaylight:nic:intent:state:transaction";
    prefix "intent-state-transaction";

    description
        "This module represents a transaction to represent Intent sate change based on events.";

    revision 2015-12-03 {
        description "Initial revision.";
    }

    grouping intent-state-transaction {
        leaf intent-id {
            type string;
            mandatory true;
            description "Intent identifier.";
        }

        leaf received-event {
            type string;
            mandatory true;
            description "Wrapper for received Intent or Network event.";
        }

        leaf executing {
            type boolean;
            mandatory false;
            description "Defines if this transaction is executing.";
        }

        leaf current-state {
            type string;
            mandatory true;
            description "Defines the current state of a given Intent.";
        }

        leaf deploy-attempts {
            type uint8;
            mandatory true;
            description "Defines the quantity of deploy attempts.";
        }

        leaf undeploy-attempts {
            type uint8;
            mandatory true;
            description "Defines the quantity of undeploy attempts.";
        }
    }

    container intent-state-transactions {
        list intent-state-transaction {
            key "intent-id";
            uses intent-state-transaction;
        }
    }
}
