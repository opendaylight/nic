module mapping-impl {
    yang-version 1;
    namespace "urn:opendaylight:params:xml:ns:yang:mapping:impl";
    prefix "mapping-impl";

    import config { prefix config; revision-date 2013-04-05; }
    import opendaylight-md-sal-binding { prefix md-sal-binding; revision-date 2013-10-28;}

    description
        "Service definition for mapping project";

    revision "2015-11-11" {
        description
            "Initial revision";
    }

    identity mapping {
        base config:module-type;
        config:java-name-prefix Mapping;
    }

    augment "/config:modules/config:module/config:configuration" {
        case mapping {
            when "/config:modules/config:module/config:type = 'mapping'";
            container broker {
                uses config:service-ref {
                    refine type {
                        mandatory true;
                        config:required-identity md-sal-binding:binding-broker-osgi-registry;
                    }
                }
            }
            container rpc-registry {
                uses config:service-ref {
                    refine type {
                        mandatory true;
                        config:required-identity md-sal-binding:binding-rpc-registry;
                    }
                }
            }
        }
    }

    // Runtime state definition for foo-impl module
    augment "/config:modules/config:module/config:state" {
        case mapping {
            when "/config:modules/config:module/config:type = 'mapping'";
        }
    }
}
