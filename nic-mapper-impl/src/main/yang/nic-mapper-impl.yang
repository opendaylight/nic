/*
 * Copyright (c) 2015 Hewlett Packard.  All rights reserved.
 *
 * This program and the accompanying materials are made available under the
 * terms of the Eclipse Public License v1.0 which accompanies this distribution,
 * and is available at http://www.eclipse.org/legal/epl-v10.html
 */

module nic-mapper-impl {
    yang-version 1;
    namespace "urn:opendaylight:nic:nic:mapper:impl";
    prefix "nic-mapper-impl";

    import config { prefix config; revision-date 2013-04-05; }
    import opendaylight-md-sal-binding { prefix mdsal; revision-date 2013-10-28; }

    description
      "This module contains the base YANG definition for the nic mapper
       implementation.";

    revision 2015-08-31 {
        description "Initial revision.";
    }

    identity nic-mapper-impl {
        base config:module-type;

        // Specifies the prefix for generated Java classes.
        config:java-name-prefix NicMapper;
    }

    // Augments the 'configuration' choice node under modules/module.
    augment "/config:modules/config:module/config:configuration" {
        case nic-mapper-impl {
            when "/config:modules/config:module/config:type = 'nic-mapper-impl'";

            container data-broker {
                uses config:service-ref {
                    refine type {
                        mandatory true;
                        config:required-identity
                          mdsal:binding-async-data-broker;
                    }
                }
            }
        }
    }
}
