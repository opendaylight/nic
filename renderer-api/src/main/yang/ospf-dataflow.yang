//-------------------------------------------------------------------------------------
// Copyright (c) 2017 Serro LLC.  All rights reserved.
//
// This program and the accompanying materials are made available under the
// terms of the Eclipse Public License v1.0 which accompanies this distribution,
// and is available at http://www.eclipse.org/legal/epl-v10.html
//-------------------------------------------------------------------------------------
module ospf-dataflow {
    namespace "urn:opendaylight:nic:renderer:api:ospf:dataflow";
    prefix "ospf-dataflow";

    revision 2017-07-25 {
        description "First revision.";
    }

    grouping ospf-interface {
        leaf interface-name {
            type string;
            mandatory true;
        }

        leaf interface-type {
            type enumeration {
                enum "p2p" {
                    value 0;
                }
            }
        }
    }

    grouping ospf-dataflow {

        leaf switch-name {
            type string;
            mandatory true;
            description "Switch name where this OSPF configuration have to be applied.";
        }

        leaf ospf-name {
            type string;
            mandatory true;
            description "Uniquely identifier for an OSPF configuration.";
        }

        list ospf-interfaces {
            key "interface-name";
            uses ospf-interface;
        }
    }

    container ospf-dataflows {
        list ospf-dataflow {
            key "switch-name";
            uses ospf-dataflow;
        }
    }
}
