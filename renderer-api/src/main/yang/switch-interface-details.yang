//-------------------------------------------------------------------------------------
// Copyright (c) 2017 Serro LLC.  All rights reserved.
//
// This program and the accompanying materials are made available under the
// terms of the Eclipse Public License v1.0 which accompanies this distribution,
// and is available at http://www.eclipse.org/legal/epl-v10.html
//-------------------------------------------------------------------------------------
module switch-interface-status {
    namespace "urn:opendaylight:nic:renderer:api:switch:interface:status";
    prefix "switch-interface-status";

    import evpn-dataflow { prefix evpn-dataflow; revision-date 2017-07-24; }

    revision 2017-08-11 {
        description "Initial revision.";
    }

    grouping aggregated-vlan {
        leaf vlan-name {
            type string;
        }

        leaf vlan-id {
            type uint32;
        }
    }

    grouping switch-interface-detail {

        leaf switch-interface-name {
            type string;
            mandatory true;
            description "Defines the Switch interface name where those VLANs were added.";
        }

        list aggregated-vlans {
            key "vlan-name";
            uses aggregated-vlan;
        }
    }

    grouping switch-interface-status {

        leaf switch-id {
            type string;
            mandatory true;
            description "Defines the Switch identifier where those VLANs were added.";
        }

        list switch-interface-details {
            key "switch-interface-name";
            uses switch-interface-detail;
        }
    }

    container switch-interfaces-status {
        list switch-interface-status {
            key "switch-id";
            uses switch-interface-status;
        }
    }
}
