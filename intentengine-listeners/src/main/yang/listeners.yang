module intentengine-listeners {
    yang-version 1;
    namespace "urn:opendaylight:nic:listeners";
    prefix "intentengine-listeners";

    import config { prefix config; revision-date 2013-04-05; }
    import opendaylight-md-sal-binding { prefix mdsal; revision-date 2013-10-28; }


    description
      "This module contains the base YANG definition for the OpenFlow Renderer
       implementation.";

    revision 2015-09-16 {
        description "Initial revision.";
    }

        // This is the definition of the service implementation as a module identity
        identity intentengine-listeners {
                base config:module-type;

                // Specifies the prefix for generated java classes.
                config:java-name-prefix ListenerProvider;
        }

        // Augments the 'configuration' choice node under modules/module.
        augment "/config:modules/config:module/config:configuration" {
            case intentengine-listeners {
                when "/config:modules/config:module/config:type = 'intentengine-listeners'";

                //wires in the data-broker service
                container data-broker {
                    uses config:service-ref {
                        refine type {
                            mandatory false;
                            config:required-identity mdsal:binding-async-data-broker;
                        }
                    }
                }

                // RPC Registry
                container rpc-registry {
                    uses config:service-ref {
                        refine type {
                            mandatory true;
                            config:required-identity mdsal:binding-rpc-registry;
                        }
                    }
                }

                // Notification service
                container notification-service {
                    uses config:service-ref {
                        refine type {
                            mandatory true;
                            config:required-identity mdsal:binding-notification-service;
                        }
                    }
                }
            }
        }

}
