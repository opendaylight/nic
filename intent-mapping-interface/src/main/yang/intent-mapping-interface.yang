/*
* Copyright (c) 2015 Inocybe Technologies
* All rights reserved.
*
* This program and the accompanying materials are made available under then
* terms of the Eclipse Public License v1.0 which accompanies this distribution,
* and is available at http://www.eclipse.org/legal/epl-v10.html
*/

module intent-mapping-interface {
    yang-version 1;
    namespace "urn:opendaylight:params:xml:ns:yang:nic:mapping";
    prefix "intent-mapping-interface";

    import config { prefix config; revision-date 2013-04-05; }

    description
        "Service definition for intent-mapping-interface module";

    revision "2015-11-11" {
        description "Initial revision of intent-mapping-mdsal model";
    }

    identity intent-mapping-interface {
            base config:service-type;
            config:java-class "org.opendaylight.nic.mapping.api.IntentMappingService";
    }

    grouping multimap {
        list outer-map {
            key "id";
            leaf id {
              type string;
            }
            list inner-map {
                leaf inner-key {
                    type string;
                }
                leaf value {
                     type string;
                }
            }
        }
    }
    container mappings {
         uses multimap;
     }
}
