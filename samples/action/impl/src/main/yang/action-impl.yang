module action-impl {
    yang-version 1;
    namespace "urn:opendaylight:params:xml:ns:yang:action:impl";
    prefix "action-impl";

    import config { prefix config; revision-date 2013-04-05; }
    import opendaylight-md-sal-binding { prefix md-sal-binding; revision-date 2013-10-28;}

    description
        "Service definition for action project";

    revision "2014-12-10" {
        description
            "Initial revision";
    }

    identity action-impl {
        base config:module-type;
        config:java-name-prefix Action;
    }

    augment "/config:modules/config:module/config:configuration" {
        case action-impl {
            when "/config:modules/config:module/config:type = 'action-impl'";
            container data-broker {
                uses config:service-ref {
                    refine type {
                        mandatory true;
                        config:required-identity md-sal-binding:binding-async-data-broker;
                    }
                }
            }
        }
    }
}
