//
// Copyright (c) 2017 Serro LLC.  All rights reserved.
//
// This program and the accompanying materials are made available under the
// terms of the Eclipse Public License v1.0 which accompanies this distribution,
// and is available at http://www.eclipse.org/legal/epl-v10.html
//
module bgp-renderer {
    yang-version 1;
    namespace "urn:opendaylight:nic:bgp:renderer";
    prefix "bgp-renderer";

    import config { prefix config; revision-date 2013-04-05; }

    description
        "Service definition for BGP Renderer.";

    revision "2017-05-1" {
        description "Initial revision.";
    }

    identity bgp-renderer {
        base config:service-type;
        config:java-class "org.opendaylight.nic.bgp.api.BGPRendererService";
    }
}
