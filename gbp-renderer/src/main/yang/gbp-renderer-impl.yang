/*
 * Copyright (c) 2015 Inocybe Technologies, Inc. and others.  All rights reserved.
 *
 * This program and the accompanying materials are made available under the
 * terms of the Eclipse Public License v1.0 which accompanies this distribution,
 * and is available at http://www.eclipse.org/legal/epl-v10.html
 */

module gbp-renderer-impl {
    yang-version 1;
    namespace "urn:opendaylight:nic:gbp:renderer:impl";
    prefix "gbp-renderer-impl";

    import config { prefix config; revision-date 2013-04-05; }
    import opendaylight-md-sal-binding { prefix mdsal; revision-date 2013-10-28; }

    description
      "This module contains the base YANG definition for the gbp Renderer
       implementation.";

    revision 2015-05-11 {
        description "Initial revision.";
    }

    identity gbp-renderer-impl {
        base config:module-type;

        // Specifies the prefix for generated Java classes.
        config:java-name-prefix GBPRenderer;
    }

    // Augments the 'configuration' choice node under modules/module.
    augment "/config:modules/config:module/config:configuration" {
        case gbp-renderer-impl {
            when "/config:modules/config:module/config:type = 'gbp-renderer-impl'";

            container data-broker {
                uses config:service-ref {
                    refine type {
                        mandatory true;
                        config:required-identity
                          mdsal:binding-async-data-broker;
                    }
                }
            }
        }
    }
}
