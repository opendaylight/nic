//------------------------------------------------------------------------------
// Copyright (c) 2015 Hewlett-Packard Development Company, L.P. and others.  All rights reserved.
// 
// This program and the accompanying materials are made available under the
// terms of the Eclipse Public License v1.0 which accompanies this distribution,
// and is available at http://www.eclipse.org/legal/epl-v10.html
//------------------------------------------------------------------------------

module policy-manager {

    yang-version 1;
    namespace "urn:opendaylight:params:xml:ns:yang:controller:config:policy-manager:impl";
    prefix "ibv-pm";

    import ietf-inet-types { prefix ietf; }

    organization "Hewlett-Packard";

    contact
      "Shaun and Duane";

    description
        "This module contains the base YANG definitions for
        policy-manager implementation.";

    revision "2014-12-08" {
        description 
          "Initial revision.";
    }

    typedef ActionType {
       type string;
       description "A label which identifies the type of action. All action types
                    must be registered prior to use.";
    }

    typedef TermType {
       type string;
       description "A label which identifies the type of this classifier term.
                    All term types must be registered prior to use.";
    }

    typedef TermValue {
       type int32;
       description "The value corresponding to a classifier term.";
    }

    typedef PolicyId {
       type string;
       description "An identifier which uniquely identifies a specific policy within the context
                    of a specific application and specific domain. This identifier is not guaranteed
                    to be unique outside of that scope.";
    }

    typedef AppId {
       type string;
       description "An identifier which uniquely identifies a specific application within the context
                    of a specific domain. This identifier is not guaranteed to be unique outside
                    of that scope.";
    }

    typedef DomainId {
       type string;
       description "A globally unique identifier for a specific domain.";
    }

    container domains {
       description "The set of configured policies on a per-domain, per-application basis.";

       list domain {
          description "The set of configured policies, for a specific domain, on a per-application basis.";
          key "domain-id";

          leaf domain-id {
             type DomainId;
             description "The identifier for this domain.";
          }

          list application {
             description "An application within this domain.";
             key "app-id";

             leaf app-id {
                type AppId;
                description "The identifier for this application, within the domain.";
             }

             list app-policy {
                description "A policy which has been applied by this application within this domain.";
                key "policy-id";

                leaf policy-id {
                   type PolicyId;
                   description "The identifier for this policy, within this domain and application.";
                }

                container policy {
                   description
                       "A principle which applications (or administrators) specify to guide
                       decisions on the treatment of traffic on the network. A policy is a
                       statement of intent with respect to specific communications between
                       endpoints on the network.";

                   list action {
                      key "type";
                      description "The set of actions for this policy.";

                      leaf type {
                         type ActionType;
                         mandatory true;
                         description "The type of this action.";
                      }
                      list data {
                         key "name";
                         description "Auxiliary data for this action. Content depends upon action type.";
                         leaf name {
                            type string;
                            description "The name of the parameter in this name-value pair.";
                         }
                         leaf value {
                            type string;
                            description "The value for the parameter in this name-value pair.";
                         }
                      }
                   }

                   leaf source-endpoints {
                      type string;
                      description "A logical expression which describes the attributes of source
                                   endpoint(s) to which this policy applies. The logical expression
                                   may consist of attribute values combined via the logical constructs
                                   of 'AND', 'OR', 'NOT' (or !). Logical expressions may use parenthesis
                                   for the purpose of grouping. An empty or unspecified value implies
                                   that all source endpoints should be considered a match";
                   }

                   leaf destination-endpoints {
                      type string;
                      description "A logical expression which describes the attributes of destination
                                   endpoint(s) to which this policy applies. The logical expression
                                   may consist of attribute values combined via the logical constructs
                                   of 'AND', 'OR', 'NOT' (or !). Logical expressions may use parenthesis
                                   for the purpose of grouping. An empty or unspecified value implies
                                   that all source endpoints should be considered a match";
                   }
                }
             }
          }
       }
    }
}
