//
// Copyright (c) 2017 Serro LLC.  All rights reserved.
//
// This program and the accompanying materials are made available under the
// terms of the Eclipse Public License v1.0 which accompanies this distribution,
// and is available at http://www.eclipse.org/legal/epl-v10.html
//
module external-notification {
    yang-version 1;
    namespace "urn:opendaylight:nic:external:notification";
    prefix "external-notification";

    import intent-types { prefix types; revision-date 2015-01-22; }

    description
        "This service expose a REST API to receive alerts from an external application.";

    revision "2017-05-26" {
        description "Initial revision.";
    }

    grouping external-notification {
        leaf id {
            type types:uuid;
            mandatory true;
            description "Uniquely identifier for external notifications.";
        }

        leaf external-url {
            type string;
            mandatory false;
            description "External URL to be notified for mitigated actions.";
        }

        leaf device-ip {
            type string;
            mandatory true;
            description "Device IP that threw the alert.";
        }
    }

    container external-notifications {
        list external-notification {
            key "id";
            uses external-notification;
        }
    }
}
