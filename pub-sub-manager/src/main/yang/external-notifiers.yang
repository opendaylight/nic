//
// Copyright (c) 2017 Serro LLC.  All rights reserved.
//
// This program and the accompanying materials are made available under the
// terms of the Eclipse Public License v1.0 which accompanies this distribution,
// and is available at http://www.eclipse.org/legal/epl-v10.html
//
module external-notifier {
    yang-version 1;
    namespace "urn:opendaylight:nic:external:notifier";
    prefix "external-notifier";

    description
        "This service expose a REST API to receive external URLs for subscriptions.";

    revision "2017-06-01" {
        description "Initial revision.";
    }

    grouping external-notifier {

        leaf external-url {
            type string;
            mandatory true;
            description "External URL for subscriptions.";
        }
    }

    container external-notifiers {
        list external-notifier {
            key "external-url";
            uses external-notifier;
        }
    }
}
