//
// Copyright (c) 2017 Serro LLC.  All rights reserved.
//
// This program and the accompanying materials are made available under the
// terms of the Eclipse Public License v1.0 which accompanies this distribution,
// and is available at http://www.eclipse.org/legal/epl-v10.html
//
module external-subscriber {
    yang-version 1;
    namespace "urn:opendaylight:nic:external:subscriber";
    prefix "external-subscriber";

    import intent-types { prefix types; revision-date 2015-01-22; }

    description
        "This service expose a REST API to receive subscriptions from external applications for NIC events.";

    revision "2017-05-31" {
        description "Initial revision.";
    }

    grouping external-subscriber {
        leaf id {
            type types:uuid;
            mandatory false;
            description "Uniquely identifier for external subscribers.";
        }

        leaf external-url {
            type string;
            mandatory true;
            description "External URL to be notified for mitigated actions.";
        }
    }

    container external-subscribers {
        list external-subscriber {
            key "id";
            uses external-subscriber;
        }
    }
}
