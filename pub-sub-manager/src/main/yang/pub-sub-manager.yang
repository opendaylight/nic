//
// Copyright (c) 2017 Serro LLC.  All rights reserved.
//
// This program and the accompanying materials are made available under the
// terms of the Eclipse Public License v1.0 which accompanies this distribution,
// and is available at http://www.eclipse.org/legal/epl-v10.html
//
module pub-sub-manager {
    yang-version 1;
    namespace "urn:opendaylight:nic:pubsub:manager";
    prefix "pub-sub-manager";

    import config { prefix config; revision-date 2013-04-05; }

    description
        "Publish and Subscribe module for external applications get noticed about NIC events.";

    revision "2017-05-25" {
        description "Initial revision.";
    }

    identity pub-sub-manager-interface {
        base config:service-type;
        config:java-class "org.opendaylight.nic.pubsub.api.PubSubService";
    }
}
