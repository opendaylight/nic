/*
 * Copyright (c) 2015 NEC Corporation
 * All rights reserved.
 *
 * This program and the accompanying materials are made available under the
 * terms of the Eclipse Public License v1.0 which accompanies this
 * distribution, and is available at http://www.eclipse.org/legal/epl-v10.html
 */

module vtn-renderer {
    yang-version 1;
    namespace "urn:opendaylight:nic:vtn:renderer";
    prefix vtn-renderer;

    import config { prefix config; revision-date 2013-04-05; }
    import opendaylight-md-sal-binding { prefix md-sal-binding; revision-date 2013-10-28;}

    description
      "This module contains the base YANG definition for the VTN Renderer
       implementation.";

    revision 2015-05-08 {
        description "Initial revision.";
    }

    identity vtn-renderer {
        base config:module-type;

        // Specifies the prefix for generated Java classes.
        config:java-name-prefix VTNRenderer;
    }

    // Augments the 'configuration' choice node under modules/module.
    augment "/config:modules/config:module/config:configuration" {
        case vtn-renderer {
            when "/config:modules/config:module/config:type = 'vtn-renderer'";
            container broker {
                uses config:service-ref {
                    refine type {
                        mandatory true;
                        config:required-identity
                           md-sal-binding:binding-broker-osgi-registry;
                    }
                }
            }
        }
    }
}
