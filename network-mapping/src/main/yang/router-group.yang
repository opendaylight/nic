//---------------------------------------------------------------------------
// Copyright (c) 2017 Serro LLC.  All rights reserved.
//
// This program and the accompanying materials are made available under the
// terms of the Eclipse Public License v1.0 which accompanies this distribution,
// and is available at http://www.eclipse.org/legal/epl-v10.html
//---------------------------------------------------------------------------
module router-group {
    yang-version 1;
    namespace "urn:opendaylight:nic:network:mapping:router:group";
    prefix "router-group";

    grouping router-group {
        leaf router-group-id {
            type string;
            mandatory true;
            description "Uniquely identifier for Router Group.";
        }

        list routers-id {
            key "router-id";
            leaf router-id {
                type string;
            }
        }
    }

    container router-groups {
        list router-group {
            key "router-group-id";
            uses router-group;
        }
    }
}
