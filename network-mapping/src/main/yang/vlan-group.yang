//-------------------------------------------------------------------------------------
// Copyright (c) 2017 Serro LLC.  All rights reserved.
//
// This program and the accompanying materials are made available under the
// terms of the Eclipse Public License v1.0 which accompanies this distribution,
// and is available at http://www.eclipse.org/legal/epl-v10.html
//-------------------------------------------------------------------------------------
module vlan-group {
    yang-version 1;
    namespace "urn:opendaylight:nic:network:mapping:vlan:group";
    prefix "vlan-group";

    import vlan-info { prefix vlan-info; revision-date 2017-07-21; }
    import switch-info {prefix switch-info; revision-date 2017-07-11; }

    revision 2017-07-24 {
        description "Initial revision.";
    }

    grouping vlan {
        leaf vlan-name {
            type vlan-info:vlan-name;
        }
    }

    grouping vlan-group {

        leaf vlan-group-name {
            type string;
            mandatory true;
            description "Defines a uniquely identifier for a VLAN Group.";
        }

        list vlan-names {
            key "vlan-name";
            uses vlan;
        }

        leaf switch-name {
            type switch-info:switch-name;
            mandatory true;
            description "Uniquely identifier for a switch";
        }
    }

    container vlan-groups {
        list vlan-group {
            key "vlan-group-name";
            uses vlan-group;
        }
    }
}
