//-------------------------------------------------------------------------------------
// Copyright (c) 2017 Serro LLC.  All rights reserved.
//
// This program and the accompanying materials are made available under the
// terms of the Eclipse Public License v1.0 which accompanies this distribution,
// and is available at http://www.eclipse.org/legal/epl-v10.html
//-------------------------------------------------------------------------------------
module vlan-info {
    namespace "urn:opendaylight:nic:network:mapping:vlan:info";
    prefix "vlan-info";

    import switch-info { prefix switch; revision-date 2017-07-11; }

    revision 2017-07-21 {
        description "Initial revision.";
    }

    typedef vlan-name {
        type string;
    }

    grouping vlan-info {

        leaf name {
            type vlan-name;
            mandatory true;
            description "Uniquely identifier for a given VLAN ID.";
        }

        leaf vlan-id {
            type uint8;
            mandatory true;
            description "VLAN Id.";
        }
    }

    container vlan-infos {
        list vlan-info {
            key "name";
            uses vlan-info;
        }
    }
}
