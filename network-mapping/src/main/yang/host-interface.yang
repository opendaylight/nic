//-------------------------------------------------------------------------------------
// Copyright (c) 2017 Serro LLC.  All rights reserved.
//
// This program and the accompanying materials are made available under the
// terms of the Eclipse Public License v1.0 which accompanies this distribution,
// and is available at http://www.eclipse.org/legal/epl-v10.html
//-------------------------------------------------------------------------------------
module host-interface {
    namespace "urn:opendaylight:nic:network:mapping:host:interface";
    prefix "host-interface";

    import bridge-info { prefix bridge-info; revision-date 2017-07-31; }

    revision 2017-07-31 {
        description "Initial revision.";
    }

    typedef interface-name {
        type string;
    }

    grouping host-interface {

        leaf interface-name {
            type interface-name;
            mandatory true;
            description "Defines the interface name. ie: eth0; eth1";
        }

        leaf switch-interface {
            type string;
            mandatory true;
            description "Defines the switch interface where this host interface is connected. ie: xe-0/0/2";
        }

        list bridges {
            key "bridge-name";
            uses bridge-info:interface-bridges;
        }
    }
}
