//---------------------------------------------------------------------------
// Copyright (c) 2017 Serro LLC.  All rights reserved.
//
// This program and the accompanying materials are made available under the
// terms of the Eclipse Public License v1.0 which accompanies this distribution,
// and is available at http://www.eclipse.org/legal/epl-v10.html
//---------------------------------------------------------------------------
module pod-info {
    yang-version 1;
    namespace "urn:opendaylight:nic:network:mapping:pod:info";
    prefix "pod-info";

    description
        "This module defines the basic information of a given POD.";

    grouping pod-info {
        leaf id {
            type string;
            mandatory true;
            description "Defines the POD id such as <service-name>_<hos-name>";
        }
    }

    container pod-infos {
        list pod-info {
            key "id";
            uses pod-info;
        }
    }
}
