//-------------------------------------------------------------------------------------
// Copyright (c) 2017 Serro LLC.  All rights reserved.
//
// This program and the accompanying materials are made available under the
// terms of the Eclipse Public License v1.0 which accompanies this distribution,
// and is available at http://www.eclipse.org/legal/epl-v10.html
//-------------------------------------------------------------------------------------
module bridge-info {
    namespace "urn:opendaylight:nic:network:mapping:bridge:info";
    prefix "bridge-info";

    revision 2017-07-31 {
        description "Initial revision.";
    }

    typedef bridge-name {
        type string;
    }

    typedef vlan-name {
        type string;
    }

    grouping interface-bridges {
        leaf bridge-name {
            type bridge-name;
        }

        leaf vlan-name {
            type vlan-name;
            mandatory true;
            description "Defines the VLAN Name associated with this bridge.";
        }

        leaf vlan-id {
            type uint16;
            mandatory true;
            description "Defines the VLAN ID associated with this bridge.";
        }
    }
}
