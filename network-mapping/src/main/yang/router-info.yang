//-------------------------------------------------------------------------------------
// Copyright (c) 2017 Serro LLC.  All rights reserved.
//
// This program and the accompanying materials are made available under the
// terms of the Eclipse Public License v1.0 which accompanies this distribution,
// and is available at http://www.eclipse.org/legal/epl-v10.html
//-------------------------------------------------------------------------------------
module router-info {
    yang-version 1;
    namespace "urn:opendaylight:nic:network:mapping:router:info";
    prefix "router-info";

    import ietf-inet-types { prefix "inet"; }

    revision "2017-06-13" {
        description "Initial revision.";
    }

    grouping router-info {

        leaf router-info-id {
            type string;
            mandatory true;
            description "Uniquely identifier for Router Info.";
        }

        leaf service-peer-ip {
            type string;
            mandatory true;
            description "Service Peer IP.";
        }

        leaf asn {
            type uint32;
            mandatory true;
            description "Autonomous System Number.";
        }

        leaf vendor {
            type string;
            mandatory false;
            description "Specify the router vendor. If no vendor is specified, the standard configuration will be used.";
        }

        leaf model {
            type string;
            mandatory false;
            description "Specify the router model.";
        }

        leaf peer-path-id {
            type uint32;
            mandatory true;
            description "Specify the Peer PathId.";
        }

        list prefix-list {
            key "order";
            leaf order {
                type uint8;
            }

            choice prefix {
                case prefixes {
                    container prefix {
                        uses prefixes;
                    }
                }
            }
        }
    }

    grouping prefixes {
        leaf prefix {
            type inet:ipv4-prefix;
            description "Represents the prefix advertised to a given router.";
        }
    }

    container router-infos {
        list router-info {
            key "router-info-id";
            uses router-info;
        }
    }
}
