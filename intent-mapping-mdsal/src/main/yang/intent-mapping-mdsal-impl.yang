/*
* Copyright (c) 2015 Inocybe Technologies
* All rights reserved.
*
* This program and the accompanying materials are made available under then
* terms of the Eclipse Public License v1.0 which accompanies this distribution,
* and is available at http://www.eclipse.org/legal/epl-v10.html
*/

module intent-mapping-mdsal-impl {
    yang-version 1;
    namespace "urn:opendaylight:params:xml:ns:yang:intent:mapping:mdsal:impl";
    prefix "intent-mapping-mdsal-impl";

    import config { prefix config; revision-date 2013-04-05; }
    import opendaylight-md-sal-binding { prefix md-sal-binding; revision-date 2013-10-28;}
    import intent-mapping { prefix mapping-svc; revision-date 2015-11-11;}

    description
        "Service definition for intent-mapping-mdsal implementation module";

    revision "2015-11-11" {
        description "Initial revision of intent-mapping-mdsal model";
    }

    identity intent-mapping-mdsal-impl {
        base config:module-type;
        config:java-name-prefix MappingMdsalImpl;
        config:provided-service mapping-svc:intent-mapping-service;
    }

    augment "/config:modules/config:module/config:configuration" {
        case intent-mapping-mdsal-impl {
            when "/config:modules/config:module/config:type = 'intent-mapping-mdsal-impl'";
            container broker {
                uses config:service-ref {
                    refine type {
                        mandatory true;
                        config:required-identity md-sal-binding:binding-broker-osgi-registry;
                    }
                }
            }
        }
    }
}
