module neutron-integration {
    yang-version 1;
    namespace "urn:opendaylight:nic:neutron:integration";
    prefix "neutron-integration";

    import config { prefix config; revision-date 2013-04-05; }
    import opendaylight-md-sal-binding { prefix mdsal; revision-date 2013-10-28; }
    import intent-impl { prefix intent-impl; revision-date 2015-05-07; }

    description
      "This module contains the base YANG definition for the integration with
       Neutron and OVSDB implementation.";

    revision 2015-11-25 {
        description "Initial revision.";
    }

        // This is the definition of the service implementation as a module identity
        identity neutron-integration {
                base config:module-type;

                // Specifies the prefix for generated java classes.
                config:java-name-prefix NeutronIntegrationProvider;
        }

        // Augments the 'configuration' choice node under modules/module.
        augment "/config:modules/config:module/config:configuration" {
            case neutron-integration {
                when "/config:modules/config:module/config:type = 'neutron-integration'";

                //wires in the data-broker service
                container data-broker {
                    uses config:service-ref {
                        refine type {
                            mandatory false;
                            config:required-identity mdsal:binding-async-data-broker;
                        }
                    }
                }

                //wires in the intent implementation
                container intent-impl {
                    uses config:service-ref {
                        refine type {
                            mandatory true;
                            config:required-identity intent-impl:nic-console-provider;
                        }
                    }
                }

            }
        }

}
