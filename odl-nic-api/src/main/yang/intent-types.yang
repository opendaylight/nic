//------------------------------------------------------------------------------
// Copyright (c) 2015 Ciena and others.  All rights reserved.
//
// This program and the accompanying materials are made available under the
// terms of the Eclipse Public License v1.0 which accompanies this distribution,
// and is available at http://www.eclipse.org/legal/epl-v10.html
//------------------------------------------------------------------------------
module intent-types {
    namespace "urn:opendaylight:intent:types";
    prefix "intent-types";

    revision 2015-01-22 {
        description "Initial revision";
    }


    // This should be pulled from yang-types, but for some reason that was
    // not working, so here is a definition.
    typedef uuid {
        type string {
            pattern "([0-9a-fA-F]{8})-([0-9a-fA-F]{4}-){3}[0-9a-fA-F]{12}";
        }
    }
}
