//------------------------------------------------------------------------------
// Copyright (c) 2015 Ciena and others.  All rights reserved.
//
// This program and the accompanying materials are made available under the
// terms of the Eclipse Public License v1.0 which accompanies this distribution,
// and is available at http://www.eclipse.org/legal/epl-v10.html
//------------------------------------------------------------------------------
module intent {
    namespace "urn:opendaylight:intent";
    prefix "intent";

    import intent-types { prefix types; revision-date 2015-01-22; }
    import intent-subjects { prefix subjects; revision-date 2015-01-22; }
    import intent-actions { prefix actions; revision-date 2015-01-22; }
    import intent-conditions { prefix conditions; revision-date 2015-01-22; }
    import intent-constraints { prefix constraints; revision-date 2015-01-22; }

    revision 2015-01-22 {
        description "Initial revision";
    }

    grouping intent {
        description "An intent specifies two or more end point groups and the connectivity
                between those end point groups. The connectivity between the end
                point groups is specified in the form of policies.";
            leaf id {
                type types:uuid;
                mandatory true;
                description "Uniquely identifies the intent";
            }

        leaf status {
            type enumeration {
                enum "pending";
                enum "completed-success";
                enum "completed-error";
            }
            config false;
            mandatory true;
            description "Represents the operational status of the request maintained by
                        the system.";
        }

        leaf detailed-status-message {
            type string;
            config false;
            mandatory false;
            description "Additional status information that is available to the client
                        such as a reason for a failure.";
        }

        list subjects {
            choice subject {
                case end-point-selector {
                    uses subjects:end-point-selector;
                }
                case end-point-group-selector {
                    uses subjects:end-point-group-selector;
                }
                case end-point-group {
                    users subject:end-point-group;
                }
            }
            min-elements 2;
            max-elements 2;
            description "List of subjectss that are part of the intent request. There
                        is an implicit many to many connection between all subjects
                        selected.";
        }
        list actions {
            choice action {
                case allow {
                    uses actions:allow;
                }
                case redirect {
                    uses actions:redirect;
                }
                case inject {
                    uses actions:inject;
                }
                case audit {
                    uses actions:audit;
                }
                case log {
                    uses actions:log;
                }
                case latency {
                    uses actions:latency;
                }
                case bandwidth {
                    uses actions:bandwidth;
                }
                case loss {
                    uses actions:loss;
                }
                case protect {
                    uses actions:protect;
                }
                case secure {
                    uses actions:secure;
                }
                case qos {
                    uses actions:qos;
                }
                case block {
                    uses actions:block;
                }
            }

            description "List of action references to apply to the connections between
                        the subjects.";
        }
        list constraints {
            choice constraints {
                case include-node {
                    uses constraints:include-node;
                }
                case exclude-node {
                    uses constraints:exclude-node;
                }
            }
            description "List of additional constraints to apply to the when implementing
                        the intent.";
        }

        list conditions {
            choice condition {
                case scheduled {
                    uses conditions:scheduled;
                }
                case weekly {
                    uses conditions:weekly;
                }
            }
            description "List of conditions when this intent will be applied.";
        }
    }

    container intents {
        list intent {
            key "id";

            uses intent;
        }
    }
}
