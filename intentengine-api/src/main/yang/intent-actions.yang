//-------------------------------------------------------------------------------------
// Copyright (c) 2015 Ciena, Hewlett-Packard, Inocybe and others.  All rights reserved.
//
// This program and the accompanying materials are made available under the
// terms of the Eclipse Public License v1.0 which accompanies this distribution,
// and is available at http://www.eclipse.org/legal/epl-v10.html
//-------------------------------------------------------------------------------------
module intent-actions {
    namespace "urn:opendaylight:intent:actions";
    prefix "intent-actions";

    revision 2015-01-22 {
        description "Initial revision";
    }

    grouping action {
        description "The action (verb) of what is to be performed by this intent.";
    }

    grouping allow {
        uses action;
        description "Indicates traffic is allowed.";
    }

    grouping block {
        uses action;
        description "Indicates traffic is not allowed";
    }

    grouping redirect {
        uses action;
        description "Indicates traffic is to redirect";
    }
}
