// Contents of "types"
module types {
    namespace "urn:opendaylight:types";
    prefix "types";

    revision 2015-01-22 {
        description "Initial revision";
    }

    typedef uuid {
        type string {
            pattern "([0-9a-fA-F]{8})-([0-9a-fA-F]{4}-){3}[0-9a-fA-F]{12}";
        }
    }
    
    typedef selector-specification {
        type string {
            pattern "[0-9a-zA-Z *]+";
        }
    }
    
    typedef identifier {
        type string {
            pattern "[_a-zA-Z][_0-9a-zA-Z]*";
        }
    }
}
