//-------------------------------------------------------------------------------------
// Copyright (c) 2015 Ciena, Hewlett-Packard, Inocybe and others.  All rights reserved.
//
// This program and the accompanying materials are made available under the
// terms of the Eclipse Public License v1.0 which accompanies this distribution,
// and is available at http://www.eclipse.org/legal/epl-v10.html
//-------------------------------------------------------------------------------------
module intent-constraints {
    namespace "urn:opendaylight:intent:constraints";
    prefix "intent-constraints";

    revision 2015-01-22 {
        description "Initial revision";
    }

    grouping constraint {
        description "The contraints (how) provide more guidelines on how the intent
                will have to be realized.";
    }

    grouping include-node {
      uses constraint;

      leaf include-selector {
        type string;
      }

      description "Constraint that requires a specific node to be included
          in a path computation.";
    }

    grouping exclude-node {
      uses constraint;

      leaf exclude-selector {
        type string;
      }

      description "Constraint that requires a specific node to be excluded
          from a path computation.";
    }

    grouping encapsulation-mpls {
        uses constraint;

        leaf label {
            type uint16;
        }

        description "Encapsulation strategy to be applied.";
    }
}
