module intent-impl {
    yang-version 1;
    namespace "urn:opendaylight:params:xml:ns:yang:intent:impl";
    prefix "intent-impl";

    import config { prefix config; revision-date 2013-04-05; }
    import opendaylight-md-sal-binding { prefix md-sal-binding; revision-date 2013-10-28;}

    description
        "Service definition for nic project";

    revision "2014-12-10" {
        description
            "Initial revision";
    }

    identity intent-impl {
        base config:module-type;
        config:java-name-prefix Intent;
    }

    augment "/config:modules/config:module/config:configuration" {
        case intent-impl {
            when "/config:modules/config:module/config:type = 'intent-impl'";
            container broker {
                uses config:service-ref {
                    refine type {
                        mandatory true;
                        config:required-identity md-sal-binding:binding-broker-osgi-registry;
                    }
                }
            }

            container notification-service {
                uses config:service-ref {
                    refine type {
                        mandatory true;
                        config:required-identity md-sal-binding:binding-notification-service;
                    }
                }
            }
        }
    }
}
