module intentengine-impl-config {
    namespace "urn:opendaylight:params:xml:ns:yang:intentengine:impl:config";
    prefix "intentengine-impl-config";

    import config { prefix config; revision-date 2013-04-05; }
    import opendaylight-md-sal-binding { prefix mdsal; revision-date 2013-10-28;}

    description
        "Service definition for the EntityEngine API project";

    revision "2015-05-07" {
        description
            "Initial revision";
    }

    identity intentengine-impl-config {
        base config:module-type;
        config:java-name-prefix NicProvider;
    }

    augment "/config:modules/config:module/config:configuration" {
        case intentengine-impl-config {
            when "/config:modules/config:module/config:type = 'intentengine-impl-config'";
            container data-broker {
                uses config:service-ref {
                    refine type {
                        mandatory true;
                        config:required-identity mdsal:binding-broker-osgi-registry;
                    }
                }
            }
        }
    }
}
