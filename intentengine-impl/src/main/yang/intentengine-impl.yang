module intentengine-impl {
    yang-version 1;
    namespace "urn:opendaylight:nic:intentengine:impl";
    prefix intentengine-impl;

    import config {
        prefix config;
        revision-date 2013-04-05;
    }
    import opendaylight-md-sal-binding {
        prefix mdsal;
        revision-date 2013-10-28;
    }

    description
      "Service definition for the EntityEngine API project.";

    revision "2015-05-07" {
        description "Initial revision.";
    }

    identity intentengine-impl {
        base config:module-type;

        // Specifies the prefix for generated Java classes.
        config:java-name-prefix NicProvider;
    }

    // Augments the 'configuration' choice node under modules/module.
    augment "/config:modules/config:module/config:configuration" {
        case intentengine-impl {
            when "/config:modules/config:module/config:type = 'intentengine-impl'";

            container data-broker {
                uses config:service-ref {
                    refine type {
                        mandatory true;
                        config:required-identity
                          mdsal:binding-async-data-broker;
                    }
                }
            }
        }
    }
}
