module mapper {
    yang-version 1;
    namespace "urn:opendaylight:params:xml:ns:yang:mapper";
    prefix "mapper";

    revision "2015-01-05" {
        description "Initial revision of mapper model";
    }
    rpc get-value {
        input {
            leaf key {
                type string;
            }
        }
        output {
            leaf result {
                type string;
            }
        }
    }
}
