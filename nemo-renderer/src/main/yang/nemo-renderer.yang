/*
 * Copyright (c) 2015 Huawei, Inc and others. All rights reserved.
 * This program and the accompanying materials are made available under the
 * terms of the Eclipse Public License v1.0 which accompanies this
 * distribution, and is available at http://www.eclipse.org/legal/epl-v10.html
 */
module nemo-renderer {

    yang-version 1;

    namespace "urn:opendaylight:nic:nemo:renderer";

    prefix nemo-renderer;

    import config {
        prefix config;
        revision-date 2013-04-05;
    }

    import opendaylight-md-sal-binding {
        prefix mdsal;
        revision-date 2013-10-28;
    }

    description
      "This module contains the base YANG definition for the
       NEMO Renderer implementation.";

    revision 2015-10-01 {
        description "Initial revision.";
    }

    identity nemo-renderer {
        base config:module-type;
        config:java-name-prefix NEMORenderer;
    }

    augment "/config:modules/config:module/config:configuration" {
        case nemo-renderer {
            when "/config:modules/config:module/config:type = 'nemo-renderer'";

            container data-broker {
                uses config:service-ref {
                    refine type {
                        mandatory true;
                        config:required-identity
                          mdsal:binding-async-data-broker;
                    }
                }
            }
            container rpc-registry {
                uses config:service-ref {
                    refine type {
                        mandatory true;
                        config:required-identity mdsal:binding-rpc-registry;
                    }
                }
            }
        }
    }
}
