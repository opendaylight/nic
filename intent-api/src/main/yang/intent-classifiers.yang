//-------------------------------------------------------------------------------------
// Copyright (c) 2015-2016 Ciena, Hewlett-Packard, Inocybe and others.  All rights reserved.
//
// This program and the accompanying materials are made available under the
// terms of the Eclipse Public License v1.0 which accompanies this distribution,
// and is available at http://www.eclipse.org/legal/epl-v10.html
//-------------------------------------------------------------------------------------
module intent-classifiers {
    namespace "urn:opendaylight:intent:classifiers";
    prefix "intent-classifiers";

    revision 2016-01-29 {
        description "Initial revision";
    }

    grouping classifier {
      leaf name {
        type string;
      }
      description "The classifier describes the application.";
    }
}
