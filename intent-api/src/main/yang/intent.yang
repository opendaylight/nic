//-------------------------------------------------------------------------------------
// Copyright (c) 2015-2016 Ciena, Hewlett-Packard, Inocybe and others.  All rights reserved.
//
// This program and the accompanying materials are made available under the
// terms of the Eclipse Public License v1.0 which accompanies this distribution,
// and is available at http://www.eclipse.org/legal/epl-v10.html
//-------------------------------------------------------------------------------------
module intent {
    namespace "urn:opendaylight:intent";
    prefix "intent";

    import intent-types { prefix types; revision-date 2015-01-22; }
    import intent-subjects { prefix subjects; revision-date 2015-01-22; }
    import intent-actions { prefix actions; revision-date 2015-01-22; }
    import intent-conditions { prefix conditions; revision-date 2015-01-22; }
    import intent-constraints { prefix constraints; revision-date 2015-01-22; }
    import intent-qos { prefix qos-config; revision-date 2015-01-22; }

    revision 2015-01-22 {
        description "Initial revision";
    }

    grouping intent {
        description "An intent specifies two subjects and a list of actions that specific
                the desired connectivity state between those subjects.";
        leaf id {
            type types:uuid;
            mandatory true;
            description "Uniquely identifies the intent";
        }

        leaf status {
            type enumeration {
                enum "pending";
                enum "completed-success";
                enum "completed-error";
            }
            config false;
            mandatory true;
            description "Represents the operational status of the request maintained by
                        the system.";
        }

        leaf state {
                    type enumeration {
                        enum "UNDEPLOYED";
                        enum "UNDEPLOYING";
                        enum "DEPLOYING";
                        enum "DEPLOYED";
                        enum "DEPLOYFAILED";
                        enum "UNDEPLOYFAILED";
                        enum "DISABLING";
                        enum "DISABLED";
                    }
                    config false;
                    mandatory true;
                    description "Represents the state of the intent.";
                }

        leaf detailed-status-message {
            type string;
            config false;
            mandatory false;
            description "Additional status information that is available to the client
                        such as a reason for a failure.";
        }

        list subjects {
            key "order";
            leaf order {
                type uint8;
            }

            choice subject {
                case end-point-selector {
                    container end-point-selector {
                        uses subjects:end-point-selector;
                    }
                }
                case end-point-group-selector {
                    container end-point-group-selector {
                        uses subjects:end-point-group-selector;
                    }
                }
                case end-point-group {
                    container end-point-group {
                        uses subjects:end-point-group;
                    }
                }
            }

            max-elements 2;
            description "List of subjects that are part of the intent request. There
                        is an implicit many to many connection between all subjects selected.";
        }
        list actions {
            key "order";
            leaf order {
                type uint8;
            }
            choice action {
                case allow {
                    container allow {
                        uses actions:allow;
                    }
                }
                case block {
                    container block {
                        uses actions:block;
                    }
                }
                case redirect {
                    container redirect {
                        uses actions:redirect;
                    }
                }
                case mirror {
                    container mirror {
                        uses actions:mirror;
                    }
                }
                case log {
                    container log {
                        uses actions:log;
                    }
                }
            }

            description "List of action references to apply to the connections between
                        the subjects.";
        }

        list qos-config {
            key "order";
            leaf order {
                type uint8;
            }
            choice qos {
                case dscp-type {
                    container dscp-type {
                        uses qos-config:dscp-type;
                    }
                }
            }
            description "List of configuration to apply to the QoS Configuration.";
        }

        list constraints {
            key "order";
            leaf order {
                type uint8;
            }
            choice constraints {
                case include-node {
                    container include-node {
                        uses constraints:include-node;
                    }
                }
                case exclude-node {
                    container exclude-node {
                        uses constraints:exclude-node;
                    }
                }
                case bandwidth-constraint {
                    container bandwidth-constraint {
                        uses constraints:bandwidth-constraint;
                    }
                }
                case protection-constraint {
                    container protection-constraint {
                        uses constraints:protection-constraint;
                    }
                }
                case failover-constraint {
                    container failover-constraint {
                        uses constraints:failover-constraint;
                    }
                }
                case classification-constraint {
                    container classification-constraint {
                        uses constraints:classification-constraint;
                    }
                }
                case qos-constraint {
                    container qos-constraint {
                        uses constraints:qos-constraint;
                    }
                }
            }
            description "List of additional constraints to apply to the when implementing
                        the intent.";
        }

        list conditions {
            key "order";
            leaf order {
                type uint8;
            }
            choice condition {
                case scheduled {
                    container scheduled {
                        uses conditions:scheduled;
                    }
                }
                case weekly {
                    container weekly {
                        uses conditions:weekly;
                    }
                }
                case daily {
                    container daily {
                        uses conditions:daily;
                    }
                }
            }
            description "List of conditions when this intent will be applied.";
        }
    }

    container intents {
        list intent {
            key "id";
            uses intent;
        }
    }
}
