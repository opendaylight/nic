//-------------------------------------------------------------------------------------
// Copyright (c) 2017 Serro LLC.  All rights reserved.
//
// This program and the accompanying materials are made available under the
// terms of the Eclipse Public License v1.0 which accompanies this distribution,
// and is available at http://www.eclipse.org/legal/epl-v10.html
//-------------------------------------------------------------------------------------
module intent-evpn {
    namespace "urn:opendaylight:intent:evpn";
    prefix intent-evpn;

    revision 2017-07-24 {
        description "Initial revision.";
    }

    grouping evpn-service {
        leaf service-name {
            type string;
            mandatory true;
            description "Defines the service to be applied for a given EVPN Intent.";
        }

        leaf vlan-name {
            type string;
            mandatory true;
            description "Defines the VLAN where this service will be applied.";
        }
    }

    grouping intent-evpn {

        leaf intent-evpn-name {
            type string;
            mandatory true;
            description "Uniquely identifier of this Intent.";
        }

        list evpn-services {
            key "service-name";
            uses evpn-service;
        }
    }

    container intent-evpns {
        list intent-evpn {
            key "intent-evpn-name";
            uses intent-evpn;
        }
    }
}
