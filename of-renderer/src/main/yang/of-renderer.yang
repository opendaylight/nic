module of-renderer {
    yang-version 1;
    namespace "urn:opendaylight:nic:of:renderer";
    prefix "of-renderer";

    import config { prefix config; revision-date 2013-04-05; }
    import opendaylight-md-sal-binding { prefix mdsal; revision-date 2013-10-28; }
    import pipeline-manager { prefix pipeline-manager; revision-date 2015-09-25; }
    import intent-mapping-interface { prefix intent-mapping-interface; revision-date 2015-11-11;}


    description
      "This module contains the base YANG definition for the OpenFlow Renderer
       implementation.";

    revision 2015-08-19 {
        description "Initial revision.";
    }

        // This is the definition of the service implementation as a module identity
        identity of-renderer {
                base config:module-type;

                // Specifies the prefix for generated java classes.
                config:java-name-prefix OFRendererProvider;
        }

        // Augments the 'configuration' choice node under modules/module.
        augment "/config:modules/config:module/config:configuration" {
            case of-renderer {
                when "/config:modules/config:module/config:type = 'of-renderer'";

                //wires in the data-broker service
                container data-broker {
                    uses config:service-ref {
                        refine type {
                            mandatory false;
                            config:required-identity mdsal:binding-async-data-broker;
                        }
                    }
                }

                container pipeline-manager {
                    uses config:service-ref {
                        refine type {
                            mandatory true;
                            config:required-identity pipeline-manager:pipeline-manager;
                        }
                    }
                }
                 container intent-mapping-interface {
                    uses config:service-ref {
                        refine type {
                            mandatory true;
                            config:required-identity intent-mapping-interface:intent-mapping-interface;
                        }
                    }
                }
                // Notification service
                 container notification-service {
                    uses config:service-ref {
                         refine type {
                          mandatory true;
                          config:required-identity mdsal:binding-notification-service;
                        }
                   }
                }
                container rpc-registry {
                    uses config:service-ref {
                        refine type {
                            mandatory true;
                            config:required-identity mdsal:binding-rpc-registry;
                        }
                    }
                }
            }
        }
}
