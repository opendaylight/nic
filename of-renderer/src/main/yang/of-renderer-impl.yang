module of-renderer-impl {
    yang-version 1;
    namespace "urn:opendaylight:nic:of:renderer:impl";
    prefix "of-renderer-impl";

    import config { prefix config; revision-date 2013-04-05; }
    import opendaylight-md-sal-binding { prefix mdsal; revision-date 2013-10-28; }

    description
        "This module contains the base YANG definitions for OF-renderer.";

    revision "2015-08-24" {
        description
            "Initial revision.";
    }

    // This is the definition of the service implementation as a module identity
    identity of-renderer-impl {
            base config:module-type;

            // Specifies the prefix for generated java classes.
            config:java-name-prefix OFRendererProvider;
    }

    // Augments the 'configuration' choice node under modules/module.  
    augment "/config:modules/config:module/config:configuration" {
        case of-renderer-impl {
            when "/config:modules/config:module/config:type = 'of-renderer-impl'";

            //wires in the data-broker service 
            container data-broker {
                uses config:service-ref {
                    refine type {
                        mandatory false;
                        config:required-identity mdsal:binding-async-data-broker;
                    }
                }
            }      
        }
    }
}
