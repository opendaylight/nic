//----------------------------------------------------------------------------------
// Copyright (c) 2015 Hewlett Packard Enterprise Development LP.  All rights reserved.
//
// This program and the accompanying materials are made available under the
// terms of the Eclipse Public License v1.0 which accompanies this distribution,
// and is available at http://www.eclipse.org/legal/epl-v10.html
//----------------------------------------------------------------------------------
module intent-graph {
    yang-version 1;
    namespace "urn:opendaylight:nic:intent:graph";
    prefix "intent-graph";

    import config { prefix config; revision-date 2013-04-05; }
    import opendaylight-md-sal-binding { prefix mdsal; revision-date 2013-10-28; }
    import intent-mapping-interface { prefix intent-mapping-interface; revision-date 2015-11-11;}

    description
      "This module is yang structure definition for PGA graph";

    revision 2015-09-11 {
        description "Initial revision";
    }

    // This is the definition of the service implementation as a module identity
    identity intent-graph {
            base config:module-type;

            // Specifies the prefix for generated java classes.
            config:java-name-prefix GraphProvider;
    }

    // Augments the 'configuration' choice node under modules/module.
    augment "/config:modules/config:module/config:configuration" {
        case intent-graph {
            when "/config:modules/config:module/config:type = 'intent-graph'";
            container intent-mapping-interface {
                uses config:service-ref {
                    refine type {
                        mandatory true;
                        config:required-identity intent-mapping-interface:intent-mapping-interface;
                    }
                }
            }
        }
    }

    typedef edge-types {
         type enumeration {
            enum must-allow {
                value 1;
                description "Strong Allow";
            }
            enum can-allow {
                value 2;
                description "Can Communicate provided there is no condition";
            }
            enum must-deny {
                value 4;
                description "Strong Block";
            }
            enum conditional {
                value 8;
                description "Good to have, but can be overrided by others";
            }
         }
         description "Graph edge for specifying intent in PGA";
    }

    typedef action-types {
             type enumeration {
                enum composable {
                    value 1;
                    description "edge-types that can be composed";
                }
                enum observer {
                    value 2;
                    description "edge-types that are used for observing";
                }
                enum exclusive {
                    value 4;
                    description "edge-types that conflict";
                }
             }
             description "Characteristics of edge-types";
        }

    container graph {
       leaf id {
         type string;
       }
       list intent-ids {
         key "intent-id";
         leaf intent-id {
             type uint8;
             description "identifying the uuid of original intent creation";
         }
       }
       list nodes {
         key "name";
         leaf name {
             type string;
             description "src-nodes are vertices which are based on label tree";
         }
       }
       list edges {
         key "identifier";
         leaf identifier {
             type string;
         }
         leaf src-node {
             type string;
         }
         leaf dst-node {
             type string;
         }
         leaf type {
             type edge-types;
         }
         leaf action-type {
             type action-types;
         }
       }
       list classifiers {
         key "classifier";
         leaf classifier {
             type string;
             description "classifiers for application description";
         }
       }
       description "The common graph structure for input and composed graph with source and destination node and edge action type";
    }
}
